-- Redis Server: SNMP Subagent
-- 
-- Copyright (C) 2011 Brice Figureau
-- Copyright (C) 2011 Days of Wonder, Inc.
--
-- This program is free software; you can redistribute it and/or
-- modify it under the terms of the GNU General Public License
-- as published by the Free Software Foundation; either version 2
-- of the License, or (at your option) any later version.
-- 
-- This program is distributed in the hope that it will be useful,
-- but WITHOUT ANY WARRANTY; without even the implied warranty of
-- MERCHANTABILITY or FITNESS FOR A PARTICULAR PURPOSE.  See the
-- GNU General Public License for more details.
-- 
-- You should have received a copy of the GNU General Public License
-- along with this program; if not, write to the Free Software
-- Foundation, Inc., 59 Temple Place - Suite 330, Boston, MA  02111-1307, USA.
--

REDIS-SERVER-MIB DEFINITIONS ::= BEGIN

IMPORTS
    MODULE-IDENTITY, OBJECT-TYPE, NOTIFICATION-TYPE,
    enterprises, Counter32, Gauge32, Unsigned32, Counter64
    FROM SNMPv2-SMI

    TEXTUAL-CONVENTION
    FROM SNMPv2-TC

    MODULE-COMPLIANCE, OBJECT-GROUP
    FROM SNMPv2-CONF;

redis		MODULE-IDENTITY
    LAST-UPDATED "201304170000Z" -- April 17, 2013
    ORGANIZATION "Days of Wonder, Inc."
    CONTACT-INFO
    "Days of Wonder
    334 State Street, Suite 203
    Los Altos, CA 94022
    USA"
    DESCRIPTION
    "This MIB describes a collection of Redis server metrics."

    REVISION "201304170000Z" -- April 17, 2013
    DESCRIPTION
    "Added additional OIDs:
      redisBlockedClients,
      redisEvictedKeys,
      redisExpiredKeys,
      redisKeyspaceHits,
      redisKeyspaceMisses,
      redisPubsubChannels,
      redisPubsubPatterns,
      redisUptime,
      redisUsedMemoryRss
    "

    REVISION "201302160000Z"	    -- Feb. 16, 2013
    DESCRIPTION
    "Added the object redisCPUSys and redisCPUUsr."

    REVISION "201302080000Z"	    -- Feb. 08, 2013
    DESCRIPTION
    "Conformance and mib validation."

    REVISION "201108150000Z"	    -- Aug. 15, 2011
    DESCRIPTION
    "The original version of this MIB."

    ::= { enterprises daysofwonder(20267) 400 }

-- Current Redis core MIB entries

REDISUnsigned64 ::= TEXTUAL-CONVENTION
    DISPLAY-HINT "d"
    STATUS  current
    DESCRIPTION
    "A 64 bits unsigned (which doesn't exist in SMIv2) containing any unsigned 64 bits
    integer number. It is defined as a Counter64 but doesn't carry the counter semantic"
    
    SYNTAX  Counter64

redisStatus		OBJECT IDENTIFIER ::= { redis 1 }

redisConnectedClients OBJECT-TYPE
    SYNTAX	Gauge32
    MAX-ACCESS	read-only
    STATUS	current
    DESCRIPTION
    "The number of clients connected to this server"
    ::= { redisStatus 1 }

redisConnectedSlaves OBJECT-TYPE
    SYNTAX	Gauge32
    MAX-ACCESS	read-only
    STATUS	current
    DESCRIPTION
    "The number of slaves connected to this server"
    ::= { redisStatus 2 }

redisUsedMemory OBJECT-TYPE
    SYNTAX	REDISUnsigned64
    UNITS "Bytes"
    MAX-ACCESS	read-only
    STATUS	current
    DESCRIPTION
    "The number of bytes allocated by redis"
    ::= { redisStatus 3 }

redisChangesSinceLastSave OBJECT-TYPE
    SYNTAX	Gauge32
    MAX-ACCESS	read-only
    STATUS	current
    DESCRIPTION
    "The number of changes since last BGSAVE"
    ::= { redisStatus 4 }

redisTotalConnections OBJECT-TYPE
    SYNTAX	Counter64
    MAX-ACCESS	read-only
    STATUS	current
    DESCRIPTION
    "The number of connections since server start"
    ::= { redisStatus 5 }

redisCommandsProcessed OBJECT-TYPE
    SYNTAX	Counter64
    MAX-ACCESS	read-only
    STATUS	current
    DESCRIPTION
    "The number of commands served since server start"
    ::= { redisStatus 6 }

redisCPUSys OBJECT-TYPE
    SYNTAX	Counter32
    MAX-ACCESS	read-only
    STATUS	current
    DESCRIPTION
    "The number of 1/100 s spent running redis sys code on the CPU"
    ::= { redisStatus 7 }

redisCPUUsr OBJECT-TYPE
    SYNTAX	Counter32
    MAX-ACCESS	read-only
    STATUS	current
    DESCRIPTION
    "The number of 1/100 s spent running redis user code on the CPU"
    ::= { redisStatus 8 }

redisBlockedClients OBJECT-TYPE
    SYNTAX Gauge32
    MAX-ACCESS read-only
    STATUS current
    DESCRIPTION
    "The number of clients pending on a blocking call (BLPOP, BRPOP, BRPOPLPUSH)."
    ::= { redisStatus 9 }

redisEvictedKeys OBJECT-TYPE
    SYNTAX Counter64
    MAX-ACCESS read-only
    STATUS current
    DESCRIPTION
    "Number of evicted keys due to maxmemory limit."
    ::= { redisStatus 10 }

redisExpiredKeys OBJECT-TYPE
    SYNTAX Counter64
    MAX-ACCESS read-only
    STATUS current
    DESCRIPTION
    "Total number of key expiration events."
    ::= { redisStatus 11 }

redisKeyspaceHits OBJECT-TYPE
    SYNTAX Counter64
    MAX-ACCESS read-only
    STATUS current
    DESCRIPTION
    "Number of successful lookup of keys in the main dictionary."
    ::= { redisStatus 12 }

redisKeyspaceMisses OBJECT-TYPE
    SYNTAX Counter64
    MAX-ACCESS read-only
    STATUS current
    DESCRIPTION
    "Number of failed lookup of keys in the main dictionary."
    ::= { redisStatus 13 }

redisPubsubChannels OBJECT-TYPE
    SYNTAX Gauge32
    MAX-ACCESS read-only
    STATUS current
    DESCRIPTION
    "Global number of pub/sub channels with client subscriptions."
    ::= { redisStatus 14 }

redisPubsubPatterns OBJECT-TYPE
    SYNTAX Gauge32
    MAX-ACCESS read-only
    STATUS current
    DESCRIPTION
    "Global number of pub/sub patterns with client subscriptions."
    ::= { redisStatus 15 }

redisUptime OBJECT-TYPE
    SYNTAX Gauge32
    UNITS "Seconds"
    MAX-ACCESS read-only
    STATUS current
    DESCRIPTION
    "Uptime of the redis server, in seconds."
    ::= { redisStatus 16 }

redisUsedMemoryRss OBJECT-TYPE
    SYNTAX	REDISUnsigned64
    UNITS "Bytes"
    MAX-ACCESS read-only
    STATUS current
    DESCRIPTION
    "Number of bytes that Redis allocated as seen by the operating system
    (a.k.a resident set size). This is the number reported by tools such as
    top and ps."
    ::= { redisStatus 17 }

-- conformance information

redisMIBConformance OBJECT IDENTIFIER ::= { redis 2 }

redisMIBCompliances OBJECT IDENTIFIER ::= { redisMIBConformance 1 }
redisMIBGroups      OBJECT IDENTIFIER ::= { redisMIBConformance 2 }

-- compliance statements

redisMIBCompliance MODULE-COMPLIANCE
    STATUS  current
    DESCRIPTION
    "The compliance statement for SNMPv2 entities which implement REDIS."
    MODULE  -- this module
    MANDATORY-GROUPS { redisGroup }
    ::= { redisMIBCompliances 1 }

-- units of conformance

redisGroup OBJECT-GROUP
    OBJECTS   {
      redisConnectedClients,
      redisConnectedSlaves,
      redisUsedMemory,
      redisChangesSinceLastSave,
      redisTotalConnections,
      redisCommandsProcessed,
      redisCPUSys,
      redisCPUUsr,
      redisBlockedClients,
      redisEvictedKeys,
      redisExpiredKeys,
      redisKeyspaceHits,
      redisKeyspaceMisses,
      redisPubsubChannels,
      redisPubsubPatterns,
      redisUptime,
      redisUsedMemoryRss
    }
    STATUS    current
    DESCRIPTION
     "The group of objects providing for management of REDIS entities."
    ::= { redisMIBGroups 1 }

END
